;;; PVOS Short-Track v0.1 experimental operator-assisted acquisition.
;;; This is not a general DWG importer and does not establish Product authority.
(vl-load-com)

(defun pvos-st-json-string (value / result index code)
  (setq result "\"" index 1)
  (while (<= index (strlen value))
    (setq code (ascii (substr value index 1)))
    (setq result
      (strcat result
        (cond
          ((= code 34) "\\\"")
          ((= code 92) "\\\\")
          ((= code 9) "\\t")
          ((= code 10) "\\n")
          ((= code 13) "\\r")
          ((< code 32) " ")
          (T (chr code)))))
    (setq index (1+ index)))
  (strcat result "\""))

(defun pvos-st-number (value) (rtos value 2 6))
(defun pvos-st-point-json (point)
  (strcat "{\"x\":" (pvos-st-number (car point))
          ",\"y\":" (pvos-st-number (cadr point)) "}"))

(defun pvos-st-lwpolyline-vertices (entity / data vertices item)
  (setq data (entget entity) vertices nil)
  (foreach item data
    (if (= (car item) 10)
      (setq vertices (append vertices (list (cdr item))))))
  vertices)

(defun pvos-st-flat-closed-lwpolyline-p (entity / data normal elevation)
  (setq data (entget entity)
        normal (cdr (assoc 210 data))
        elevation (cond ((cdr (assoc 38 data))) (0.0)))
  (and (= (cdr (assoc 0 data)) "LWPOLYLINE")
       (= 1 (logand 1 (cdr (assoc 70 data))))
       (< (abs elevation) 0.000001)
       (or (null normal)
           (and (< (abs (car normal)) 0.000001)
                (< (abs (cadr normal)) 0.000001)
                (< (abs (- (caddr normal) 1.0)) 0.000001)))
       (not (vl-some '(lambda (item) (and (= (car item) 42) (/= (cdr item) 0.0))) data))))

(defun pvos-st-axis-segment (selection / entity pick data type closest parameter index endparam)
  (setq entity (car selection)
        pick (trans (cadr selection) 1 0)
        data (entget entity)
        type (cdr (assoc 0 data)))
  (cond
    ((= type "LINE")
      (list (vlax-curve-getStartPoint entity) (vlax-curve-getEndPoint entity)))
    ((and (= type "LWPOLYLINE")
          (not (vl-some '(lambda (item) (and (= (car item) 42) (/= (cdr item) 0.0))) data)))
      (setq closest (vlax-curve-getClosestPointTo entity pick)
            parameter (vlax-curve-getParamAtPoint entity closest)
            index (fix parameter)
            endparam (vlax-curve-getEndParam entity))
      (if (>= index endparam) (setq index (1- (fix endparam))))
      (list (vlax-curve-getPointAtParam entity index)
            (vlax-curve-getPointAtParam entity (1+ index))))
    (T nil)))

(defun pvos-st-write-project (path partition vertices axis width length orientation gapx gapy margin reference-count / file first angle)
  (setq file (open path "w")
        angle (* 180.0 (/ (angle (car axis) (cadr axis)) pi)))
  (write-line "{" file)
  (write-line "  \"caseId\": \"PVOS-ST-REAL-001\"," file)
  (write-line "  \"linearUnit\": \"mm\"," file)
  (write-line "  \"inputAcquisition\": {" file)
  (write-line "    \"sourceType\": \"OPERATOR_SUPPLIED_JSON\"," file)
  (write-line "    \"provenance\": \"OWNER_SUPPLIED_REAL_ENGINEERING_SOURCE / DWG / PVOS-ST-REAL-001\"," file)
  (write-line "    \"deidentification\": \"CASE_ID_ONLY\"," file)
  (write-line "    \"referenceMethod\": \"SELECTED_PARTITION_IN_OWNER_SUPPLIED_DWG\"" file)
  (write-line "  }," file)
  (write-line "  \"partitions\": [{" file)
  (write-line (strcat "    \"partitionId\": " (pvos-st-json-string partition) ",") file)
  (write-line "    \"boundary\": [" file)
  (setq first T)
  (foreach vertex vertices
    (if first (setq first nil) (write-line "," file))
    (princ (strcat "      " (pvos-st-point-json vertex)) file))
  (write-line "" file)
  (write-line "    ]," file)
  (write-line (strcat "    \"localAxis\": {\"origin\":" (pvos-st-point-json (car axis))
                      ",\"rotationDegrees\":" (pvos-st-number angle) "},") file)
  (write-line "    \"module\": {" file)
  (write-line (strcat "      \"physicalWidthMm\":" (pvos-st-number width) ",") file)
  (write-line (strcat "      \"physicalLengthMm\":" (pvos-st-number length) ",") file)
  (write-line (strcat "      \"orientation\":" (pvos-st-json-string orientation) ",") file)
  (write-line (strcat "      \"gapXmm\":" (pvos-st-number gapx) ",") file)
  (write-line (strcat "      \"gapYmm\":" (pvos-st-number gapy) ",") file)
  (write-line (strcat "      \"edgeMarginMm\":" (pvos-st-number margin)) file)
  (write-line "    }," file)
  (write-line "    \"manualOrCadReference\": {" file)
  (write-line (strcat "      \"expectedModuleCount\":" (itoa reference-count) ",") file)
  (write-line (strcat "      \"expectedOrientation\":" (pvos-st-json-string orientation) ",") file)
  (write-line "      \"notes\":\"Operator-selected representative partition\"" file)
  (write-line "    }" file)
  (write-line "  }]" file)
  (write-line "}" file)
  (close file))

(defun c:PVOSSTEXPORT001 (/ selection entity vertices axis-selection axis partition width length orientation gapx gapy margin reference-count path)
  (prompt "\nPVOS-ST-REAL-001 experimental acquisition. Source drawing remains outside the repository.")
  (setq selection (entsel "\nSelect ONE closed, straight-segment LWPOLYLINE partition: "))
  (cond
    ((null selection) (prompt "\nBLOCKED: partition selection cancelled."))
    ((not (pvos-st-flat-closed-lwpolyline-p (car selection)))
      (prompt "\nBLOCKED: selection must be a closed, flat, non-bulged LWPOLYLINE in millimetres."))
    (T
      (setq entity (car selection)
            vertices (pvos-st-lwpolyline-vertices entity)
            axis-selection (entsel "\nSelect the Local Axis reference LINE or straight polyline segment: ")
            axis (if axis-selection (pvos-st-axis-segment axis-selection)))
      (if (or (null axis) (< (distance (car axis) (cadr axis)) 0.000001))
        (prompt "\nBLOCKED: a non-zero straight Local Axis edge is required.")
        (progn
          (setq partition (getstring T "\nPartition ID: ")
                width (getreal "\nModule physical WIDTH (mm): ")
                length (getreal "\nModule physical LENGTH (mm): "))
          (initget "WidthAlongLocalX LengthAlongLocalX")
          (setq orientation (getkword "\nOrientation [WidthAlongLocalX/LengthAlongLocalX]: ")
                gapx (getreal "\nGap X (mm): ")
                gapy (getreal "\nGap Y (mm): ")
                margin (getreal "\nExplicit edge margin (mm, enter 0 if none): ")
                reference-count (getint "\nCAD/manual module count for this partition: "))
          (if (or (= partition "") (null width) (null length) (null orientation)
                  (null gapx) (null gapy) (null margin) (null reference-count)
                  (<= width 0.0) (<= length 0.0) (< gapx 0.0) (< gapy 0.0)
                  (< margin 0.0) (< reference-count 0))
            (prompt "\nBLOCKED: all parameters are required and must be within the governed ranges.")
            (progn
              (setq path (getfiled "Save PVOS-ST-REAL-001 project input"
                            "PVOS-ST-REAL-001-project-input.json" "json" 1))
              (if path
                (progn
                  (pvos-st-write-project path partition vertices axis width length orientation gapx gapy margin reference-count)
                  (prompt (strcat "\nPASS: wrote " path)))
                (prompt "\nBLOCKED: output save cancelled."))))))))
  (princ))

(prompt "\nLoaded PVOS-ST-REAL-001 exporter. Run PVOSSTEXPORT001.")
(princ)
